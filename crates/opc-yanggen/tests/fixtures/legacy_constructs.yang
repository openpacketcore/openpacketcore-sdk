module legacy {
  yang-version 1.1;
  namespace "urn:example:legacy";
  prefix lg;
  revision 2026-10-12;
  container root {
    container match { leaf enabled { type boolean; } }
    leaf-list type { type string; }
    leaf enabled { type boolean; default true; }
    leaf count { type uint16 { range '1..max'; } default 1; }
    leaf total { type uint32; }
    leaf signed { type int64 { range 'min..max'; } }
    leaf ratio { type decimal64 { fraction-digits 2; } }
    leaf empty { type empty; }
    leaf name { type string; }
    leaf reference { type leafref { path '/lg:root/lg:name'; } }
    leaf chained-reference { type leafref { path '/lg:root/lg:reference'; } }
    leaf-list references { type leafref { path '/lg:root/lg:reference'; } }
    leaf mode { type enumeration { enum first; enum second; } }
    list server {
      key 'name port';
      ordered-by user;
      leaf name { type string; }
      leaf port { type uint16; }
      leaf secret { type string; }
      list hop { key 'name'; leaf name { type string; } }
    }
    leaf-list preference { type string; ordered-by user; }
    leaf-list api-token { type string; ordered-by user; }
    leaf-list ratios { type decimal64 { fraction-digits 2; } ordered-by user; }
    container state { config false; leaf count { type uint32; } }
    container yang-uint64 { leaf label { type string; } }
  }
}
