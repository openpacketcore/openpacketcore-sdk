module cardinality-patch {
  yang-version 1.1;
  namespace "urn:example:cardinality-patch";
  prefix p;
  container root {
    leaf first { type uint8 { range "1..10"; } mandatory true; }
    leaf second { type string { length "1..8"; } mandatory true; }
    leaf-list codes { type string; min-elements 1; max-elements 2; ordered-by user; }
  }
}
